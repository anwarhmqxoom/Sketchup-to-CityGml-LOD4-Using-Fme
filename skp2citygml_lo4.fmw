FME workspace skp2citygml_lo4.fmw

Parameters:
- DestDataset_CITYGML_5 = $(FME_MF_DIR)xml\KIU_Dec_model_test_6.xml   # Destination CityGML Document
- SourceDataset_JPEG = $(FME_MF_DIR)skp\BrickLargeBlocks0034_200.jpg   # Source JPEG File(s)
- SourceDataset_JPEG_3 = $(FME_MF_DIR)skp\teak-doors-500x500.jpg   # Source JPEG File(s)
- SourceDataset_SKP_5 = C:\Users\munawarhussain\Desktop\computer science campus\Testing_lod9.skb   # Source Trimble SketchUp File

Readers:
- JPEG_1: JPEG from $(SourceDataset_JPEG) in EPSG:24370
- JPEG_2: JPEG from $(SourceDataset_JPEG_3) in EPSG:24370
- SKP_1: SKP from $(SourceDataset_SKP_5) in EPSG:24370

Writers:
- CITYGML_1: CITYGML to $(DestDataset_CITYGML_5) in EPSG:24370

GeometryCoercer
    KIND = fme_multi
    GQUERY:
      for $geom in //geometry
      where $geom/count(parent::geometry) = 0
      return number($geom/@fme_id)
    COERCED -> Deaggregator_3
Deaggregator_3
    PART_NUMBER_FIELD = _part_number
    SPLIT_COMPOSITES = No
    GEOM_NAME_FIELD = _geometry_name
    LIST_ATTR_MODE_LOOKUP = LEAN
    EXPLODE_INSTANCES = No
    MODE = Flatten One Level
    DEAGGREGATED -> GeometryFilter_3
GeometryFilter_3
    BREAK_AGG = No
    GEOM_PORT_NAMES = Arc
PathSplitter
    SEGMENT_NUMBER_ATTR = _segment_number
    -> Deaggregator_2
Deaggregator_2
    PART_NUMBER_FIELD = _part_number
    SPLIT_COMPOSITES = No
    GEOM_NAME_FIELD = _geometry_name
    LIST_ATTR_MODE_LOOKUP = LEAN
    EXPLODE_INSTANCES = No
    MODE = Flatten One Level
    DEAGGREGATED -> GeometryExtractor_2
GeometryExtractor_2
    ATTR = _geometry
    OGC_WKT_PRECISION_DISPLAY = Shortened 64-bit
    PREFER_POLYGON_OVER_SURFACE = No
    REMOVE_GEOMETRY = No
    OGEOSMS_URL_PREFIX = http://maps.google.com/?q=
    OGCVERSION = 1.2
    KIND_LONG = FME Binary
GeometryFilter_2
    INSTANTIATE = Yes
    BREAK_AGG = Yes
    GEOM_PORT_NAMES = Arc
GeometryExtractor_3
    ATTR = _geometry
    OGC_WKT_PRECISION_DISPLAY = Shortened 64-bit
    PREFER_POLYGON_OVER_SURFACE = No
    REMOVE_GEOMETRY = No
    OGEOSMS_URL_PREFIX = http://maps.google.com/?q=
    OGCVERSION = 1.2
    KIND_LONG = FME Binary
Inspector_6
GeometryPropertyExtractor_2 [off]
    PREFIX_EXTRACTED_TRAITS = No
    EXTRACTTYPE_PARAM = Traits
Testing_lod9 (reader SKP_1)
    -> SketchupLayerExtractor_2
SketchupLayerExtractor_2
    Extracted -> AttributeSplitter
AttributeSplitter
    LIST_NAME = _hierarchy
    ATTR_NAME = sketchup_extracted_layer
    DELIMITER = _
    TRIM_OPTION = Both
    DROP_EMPTY_PARTS = No
    -> ListElementCounter
ListElementCounter
    LIST_NAME = _hierarchy{}
    CNT_ATTR = _hierarchy_count
    -> Test_2_Levels
    -> Test_3_Levels
    -> Test_1_Level
    -> Test_4_Levels_3
    -> Test_4_Levels_2
AttributeFilter_Building_-__AttributeCreator_18_Output_-__Aggregator_11: Junction
    -> AttributeRemover_5
    -> AttributeSwapper_4
AttributeSwapper_4
    CONDITION = UNCONDITIONAL
    ATTR_A = gml_id
    ATTR_B = gml_parent_id
    COMP_MODE = Automatic
    -> AttributeRemover_3
AttributeRemover_3
    -> AttributeFilter_Building_-__AttributeCreator_18 [off]
AttributeRemover_5
    LIST_ATTRS = featureList{}
    REMOVE_ATTRS = featureList{3}
    -> Aggregator_15
Aggregator_15
    ORDERED = No
    MODE = Geometry - Assemble One Level
    SEP = ,
    ACCUM_ATTRS_NAME = Use Attributes From One Feature
    GROUP_BY = Grand_Parent_id
    AGGREGATE_TYPE = Homogeneous Collection (If Possible)
    AGGREGATE -> Inspector_2
Inspector_2 [off]
Address (writer CITYGML_1)
    attributes: citygml_target_uri xml_buffer, citygml_feature_role xml_buffer, citygml_feature_role_attr_name xml_buffer, citygml_feature_role_attr_val xml_buffer, gml_description xml_buffer, gml_name xml_buffer, citygml_address xml_xml
GroundSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
RoofSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
CityGML_Role_Setter
    ROLE = consistsOfBuildingPart
    -> CityGML_LOD_Setter_4 [off]
    -> CityGML_LOD_Setter_8 [off]
    -> CityGML_LOD_Setter_9 [off]
CityGML_LOD_Setter_4 [off]
    GEOM = lod4MultiSurface
    LOD = 4
    -> CityGML_LOD_Setter_4_Output_-__Scaler [off]
BuildingPart (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer
AttributeCreator_20_OUTPUT_-__AppearanceSetter_GEOMETRY: Junction
    -> Building (writer CITYGML_1)
Window (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer
BuildingInstallation (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_level_of_detail{} xml_buffer
IntBuildingInstallation (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_level_of_detail{} xml_buffer
CeilingSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
InteriorWallSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
Scaler
    YSCALE = 0.025
    TEXT_LOC_ONLY = Location and Size
    RASTER_SCALING = Extents
    ZSCALE = 0.025
    SCALE_ORIGIN = 0,0
    XSCALE = 0.025
    SCALED -> Offsetter_2
Offsetter_2
    XOFF = 2983460.574962016
    YOFF = 2178874.46332786
    ZOFF = 0
    MODE = Cartesian Coordinate
    OFFSET -> CoordinateSystemSetter
CoordinateSystemSetter
    COORDSYS = EPSG:24370
    -> CoordinateRounder
FloorSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
SolitaryVegetationObject (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_species xml_buffer, citygml_height xml_real64, citygml_height_units xml_buffer, citygml_trunk_diameter xml_real64, citygml_trunk_diameter_units xml_buffer, citygml_crown_diameter xml_real64, citygml_crown_diameter_units xml_buffer, citygml_level_of_detail{} xml_buffer
Road (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer
CityGMLGeometrySetter_3
    GEOM = lod4MultiSurface
    ROLE = cityObjectMember
    -> CityGML_LOD_Setter_20
CityGML_LOD_Setter_20
    GEOM = lod4Geometry
    LOD = 4
    -> CityFurniture (writer CITYGML_1)
CityFurniture (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_level_of_detail{} xml_buffer
Aggregator_21
    ORDERED = No
    MODE = Geometry - Assemble One Level
    SEP = ,
    ACCUM_ATTRS_NAME = Yes
    GROUP_BY = gml_parent_id
    AGGREGATE_TYPE = Homogeneous Collection (If Possible)
    AGGREGATE -> Counter
Counter
    DOMAIN = counter
    CNT_ATTR = _count
    SCOPE = Global
    START = 0
    -> AttributeConcatenator
AttributeConcatenator
    CASE = No
    DEST_ATTR = gml_id
    ORDER = ValueNumericAscending
    TRIM_OPTION = Both
    DROP_EMPTY_PARTS = No
    ATTRS = gml_id _count
    -> CityGML_Role_Setter_18
CityGML_Role_Setter_18
    ROLE = interiorRoom
    -> CityGML_LOD_Setter_24
CityGML_LOD_Setter_24
    GEOM = lod4MultiSurface
    LOD = 4
    -> AttributeSwapper_2
AttributeSwapper_2
    CONDITION = UNCONDITIONAL
    ATTR_A = gml_id
    ATTR_B = gml_parent_id
    COMP_MODE = Automatic
    -> AttributeSwapper_3
AttributeSwapper_3
    CONDITION = UNCONDITIONAL
    ATTR_A = gml_parent_id
    ATTR_B = Grand_Parent_id
    COMP_MODE = Automatic
    -> AttributeCreator_22
AttributeCreator_22
    ATTR_TABLE:
      SET_TO citygml_class_codeSpace = https://www.sig3d.org/codelists/citygml/2.0/building/2.0/Room_class.xml
      SET_TO citygml_function_codeSpace = https://www.sig3d.org/codelists/citygml/2.0/building/2.0/Room_function.xml
      SET_TO citygml_usage_codeSpace = https://www.sig3d.org/codelists/citygml/2.0/building/2.0/Room_usage.xml
    -> Room (writer CITYGML_1)
Room (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_level_of_detail{} xml_buffer, citygml_bounded_by{}.xlink_href xml_buffer, citygml_interior_furniture{}.xlink_href xml_buffer, citygml_room_installation{}.xlink_href xml_buffer
Aggregator_24
    ORDERED = No
    MODE = Geometry - Assemble One Level
    SEP = ,
    ACCUM_ATTRS_NAME = Use Attributes From One Feature
    GROUP_BY = Grand_Parent_id
    AGGREGATE_TYPE = Homogeneous Collection (If Possible)
    AGGREGATE -> AttributeCreator_25
AttributeCreator_25
    ATTR_TABLE = SET_TO citygml_class = @Value(mappedFeature)
    -> GeometryRemover_2
GeometryRemover_2
    -> AttributeRemover_2
AttributeRemover_2
    REMOVE_ATTRS = fme_geometry,multi_reader_full_id,mappedFeature,skp_type,multi_reader_id,sketchup_extracted_layer,fme_secondary_axis,fme_sweep_angle,_hierarchy_count,fme_primary_axis,fme_basename,fme_color,fme_fill_color,fme_rotation,multi_reader_type,feature,multi_reader_keyword,fme_text_size,fme_type,fme_feature_type,fme_start_angle,fme_text_string,fme_dataset,extractSemantic
    -> Inspector_3
Inspector_3 [off]
Aggregator_18
    ORDERED = No
    MODE = Geometry - Assemble One Level
    SEP = ,
    ACCUM_ATTRS_NAME = Yes
    GROUP_BY = gml_id
    AGGREGATE_TYPE = Homogeneous Collection (If Possible)
    AGGREGATE -> CityGML_Role_Setter_16
CityGML_Role_Setter_16
    ROLE = auxiliaryTrafficArea
    -> CityGML_LOD_Setter_21
CityGML_LOD_Setter_21
    GEOM = lod4MultiSurface
    LOD = 4
    -> Track (writer CITYGML_1)
Track (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_function{} xml_buffer, citygml_usage{} xml_buffer, citygml_traffic_area{}.xlink_href xml_buffer, citygml_auxiliary_traffic_area{}.xlink_href xml_buffer, citygml_level_of_detail{} xml_buffer
RasterBandRemover
Aggregator_19
    ORDERED = No
    MODE = Geometry - Assemble One Level
    SEP = ,
    ACCUM_ATTRS_NAME = Yes
    GROUP_BY = gml_id
    AGGREGATE_TYPE = Homogeneous Collection (If Possible)
    AGGREGATE -> CityGMLGeometrySetter_4
CityGMLGeometrySetter_4
    GEOM = lod4MultiSurface
    ROLE = cityObjectMember
    -> CityGML_LOD_Setter_22
CityGML_LOD_Setter_22
    GEOM = lod4MultiSurface
    LOD = 4
    -> PlantCover (writer CITYGML_1)
PlantCover (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_average_height xml_real64, citygml_average_height_units xml_buffer, citygml_level_of_detail{} xml_buffer
Aggregator_20
    ORDERED = No
    MODE = Geometry - Assemble One Level
    SEP = ,
    ACCUM_ATTRS_NAME = Yes
    GROUP_BY = gml_id
    AGGREGATE_TYPE = Homogeneous Collection (If Possible)
    AGGREGATE -> CityGML_Role_Setter_17
CityGML_Role_Setter_17
    ROLE = interiorFurniture
    -> CityGML_LOD_Setter_23
CityGML_LOD_Setter_23
    GEOM = lod4Geometry
    LOD = 4
    -> BuildingFurniture (writer CITYGML_1)
BuildingFurniture (writer CITYGML_1)
    attributes: sketchup_extracted_layer xml_char(200), _hierarchy{} xml_char(200), _hierarchy_count xml_char(200), extractSemantic xml_char(200), featureList{} xml_char(200), feature xml_char(200), mappedFeature xml_char(200), citygml_feature_role xml_buffer
AttributeSplitter_3
    LIST_NAME = _hierarchy
    ATTR_NAME = sketchup_extracted_layer
    DELIMITER = __
    TRIM_OPTION = Both
    DROP_EMPTY_PARTS = No
    -> ListElementCounter_2
ListElementCounter_2
    LIST_NAME = _hierarchy{}
    CNT_ATTR = _hierarchy_count
    -> Test_4_Levels_4
    -> Test_4_Levels_5
    -> Test_4_Levels_6
    -> Test_4_Levels_7
Test_4_Levels_4: Tester
    BOOL_OP = OR
    TEST_CLAUSE = TEST @Value(_hierarchy_count) = 1
    TEST_MODE = Automatic
    TEST_DESCRIPTION = ""
    PASSED -> AttributeCreator_26
AttributeCreator_26
    ATTR_LIST = gml_id,@Value(fme_basename)_@Value(sketchup_extracted_layer),address_id,@Value(fme_basename)__@Value(_hierarchy{0})__@Value(_hierarchy{1})
    -> AttributeCreator_30
Test_4_Levels_5: Tester
    BOOL_OP = OR
    TEST_CLAUSE = TEST @Value(_hierarchy_count) = 2
    TEST_MODE = Automatic
    TEST_DESCRIPTION = ""
    PASSED -> AttributeCreator_27
AttributeCreator_27
    ATTR_LIST = gml_id,@Value(fme_basename)_@Value(sketchup_extracted_layer),address_id,@Value(fme_basename)__@Value(_hierarchy{0})__@Value(_hierarchy{1})__@Value(_hierarchy{2})
    -> AttributeCreator_30
Test_4_Levels_6: Tester
    BOOL_OP = OR
    TEST_CLAUSE = TEST @Value(_hierarchy_count) = 3
    TEST_MODE = Automatic
    TEST_DESCRIPTION = ""
    PASSED -> AttributeCreator_28
AttributeCreator_28
    ATTR_LIST = gml_id,@Value(fme_basename)_@Value(sketchup_extracted_layer),address_id,@Value(fme_basename)__@Value(_hierarchy{0})__@Value(_hierarchy{1})__@Value(_hierarchy{1})__@Value(_hierarchy{2})__@Value(_hierarchy{3})
    -> AttributeCreator_30
Test_4_Levels_7: Tester
    BOOL_OP = OR
    TEST_CLAUSE = TEST @Value(_hierarchy_count) = 4
    TEST_MODE = Automatic
    TEST_DESCRIPTION = ""
    PASSED -> AttributeCreator_29
AttributeCreator_29
    ATTR_LIST = gml_id,@Value(fme_basename)_@Value(sketchup_extracted_layer),address_id,@Value(fme_basename)__@Value(_hierarchy{0})__@Value(_hierarchy{1})__@Value(_hierarchy{2})__@Value(_hierarchy{3})__@Value(_hierarchy{4})
    -> AttributeCreator_30
AttributeCreator_30
    ATTR_LIST = extractSemantic,@Value(_hierarchy{@Evaluate(@Value(__hierarchy__count)-1)})
    -> Tester_2
Tester_2
    BOOL_OP = OR
    TEST_CLAUSE = TEST @Value(extractSemantic) BEGINS_WITH b
    TEST_MODE = Automatic
    TEST_DESCRIPTION = ""
GeometryExtractor
    ATTR = _geometry
    OGC_WKT_PRECISION_DISPLAY = Shortened 64-bit
    PREFER_POLYGON_OVER_SURFACE = No
    REMOVE_GEOMETRY = No
    OGEOSMS_URL_PREFIX = http://maps.google.com/?q=
    OGCVERSION = 1.2
    KIND_LONG = FME Binary
    -> CityGMLGeometrySetter
CityGMLGeometrySetter
    GEOM = lod4MultiSurface
    ROLE = cityObjectMember
AttributeCreator_7
    ATTR_LIST = gml_id,@Value(fme_basename),mapperfeature,Building,gml_name,@Value(fme_basename)
    -> CoordinateRounder [off]
    -> Building (writer CITYGML_1) [off]
CoordinateRounder
    ZPREC = 4
    XPREC = 4
    YPREC = 4
    ROUNDED -> Inspector [off]
Inspector [off]
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_class xml_buffer, citygml_function{} xml_buffer, citygml_usage{} xml_buffer, citygml_year_of_construction xml_buffer, citygml_year_of_demolition xml_buffer, citygml_roof_type xml_buffer, citygml_measured_height xml_real64, citygml_measured_height_units xml_buffer, citygml_storeys_above_ground xml_uint64, citygml_storeys_below_ground xml_uint64, citygml_storey_heights_above_ground xml_buffer, citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer,
      citygml_level_of_detail{} xml_buffer, citygml_interior_room{}.xlink_href xml_buffer, citygml_consists_of_building_part{}.xlink_href xml_buffer, citygml_address{}.xlink_href xml_buffer
BoundsExtractor
    XMIN = _xmin
    ZMAX = _zmax
    YMAX = _ymax
    ZMIN = _zmin
    XMAX = _xmax
    YMIN = _ymin
    -> ExpressionEvaluator
ExpressionEvaluator
    ACTION = Create New Attribute
    VAL_ATTR = citygml_measured_height
    EXPRESSION = @Value(_zmax) - @Value(_zmin)
Aggregator_6 [off]
    ORDERED = No
    MODE = Geometry - Assemble One Level
    SEP = ,
    ACCUM_ATTRS_NAME = Merge Incoming Attributes
    GROUP_BY = gml_id
    AGGREGATE_TYPE = Homogeneous Collection (If Possible)
AppearanceStyler
    TEXTURE_U_SCALING_FACTOR = 1.0
    TEXTURE_V_OFFSET = 0.0
    TEXTURE_U_OFFSET = 0.0
    TEXTURE_U_SHEARING_FACTOR = 0.0
    TEXTURE_CENTER_U = 0.0
    APPEARANCE_NAME = @Value(fme_basename)
    DIFFUSE_COLOR = 0,0.333333,0.498039
    TEXTURE_WRAP_DISPLAY = Repeat in U and V
    TEXTURE_ROTATION_ANGLE = 0.0
    TEXTURE_V_SCALING_FACTOR = 1.0
    ALPHA = 1.0
    TEXTURE_CENTER_V = 0.0
    TEXTURE_V_SHEARING_FACTOR = 0.0
    -> AppearanceSetter [APPEARANCE]
AppearanceSetter
    TEXTURE_MAPPING_TYPE_CHOICE = Surface Normal
    TEXTURE_U_OFFSET2 = 0.0
    TEXTURE_V_OFFSET2 = 0.0
    TEXTURE_U_SCALE_FACTOR = 1.0
    SET_ON_SIDE = Front and Back Sides
    GQUERY:
      for $geom in //geometry
      where $geom/count(parent::geometry) = 0
      return number($geom/@fme_id)
    DEF_STORAGE = Create New Definitions
    USE_EXISTING_TEXTURE_COORDINATES = No
    GROUP_BY = gml_id
    TEXTURE_V_SCALE_FACTOR = 1.0
AttributeValueMapper_3
    DEFAULT_VALUE = 9998
    LUT = Btrg,2112,Büro,2020,Gar,2463,Gdehs,3044,Ghs,3045,Hotel,2071,Kiga,3065,Lagg,2143,Schu,3021,Veranst,3036,Vwg,1121,WBüro,1122,WGhs,1123,Whs,1010,Wkst,2120
    DIRECTION = Forward (Source To Destination)
    VAL_ATTR = citygml_function{0}
    SRC = NUTZ_TEXT
JPEG (reader JPEG_1) [off]
    -> AppearanceSetter_3 [APPEARANCE] [off]
AppearanceSetter_3
    TEXTURE_MAPPING_TYPE_CHOICE = Surface Normal
    TEXTURE_U_OFFSET2 = 0.0
    TEXTURE_V_OFFSET2 = 0.0
    TEXTURE_U_SCALE_FACTOR = 1.0
    SET_ON_SIDE = Front Side
    GQUERY:
      for $geom in //geometry
      where $geom/count(parent::geometry) = 0
      return number($geom/@fme_id)
    DEF_STORAGE = Create New Definitions
    USE_EXISTING_TEXTURE_COORDINATES = No
    TEXTURE_V_SCALE_FACTOR = 1.0
    -> OrientationExtractor
OrientationExtractor
    ORIENTATION = _orientation
    -> Orientor
Orientor
    KIND = LEFT_HAND_RULE
    ORIENTED -> WallSurface (writer CITYGML_1)
WallSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_opening{}.xlink_href xml_buffer
JPEG (reader JPEG_2) [off]
    -> AppearanceSetter_2 [APPEARANCE] [off]
AppearanceSetter_2
    TEXTURE_MAPPING_TYPE_CHOICE = Surface Normal
    TEXTURE_U_OFFSET2 = 0.0
    TEXTURE_V_OFFSET2 = 0.0
    TEXTURE_U_SCALE_FACTOR = 1.0
    SET_ON_SIDE = Front and Back Sides
    GQUERY:
      for $geom in //geometry
      where $geom/count(parent::geometry) = 0
      return number($geom/@fme_id)
    DEF_STORAGE = Create New Definitions
    USE_EXISTING_TEXTURE_COORDINATES = No
    TEXTURE_V_SCALE_FACTOR = 1.0
    -> DoorCounter
GenericCityObject (writer CITYGML_1)
    attributes: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
Creator [off]
    NUM = 1
    GEOMTYPE = Geometry Object
    CREATED -> AttributeCreator_17
AttributeCreator_17
    ATTR_TABLE = SET_TO gml_id = MAIN-BUILDING
    -> CityModel (writer CITYGML_1) [off]
CityModel (writer CITYGML_1)
    attributes: citygml_target_uri xml_buffer, gml_description xml_buffer, gml_name xml_buffer, gml_feature_member{}.xlink_href xml_buffer, citygml_appearance_member{}.xlink_href xml_buffer, citygml_city_object_member{}.xlink_href xml_buffer
Orientor_2
    KIND = RIGHT_HAND_RULE
    ORIENTED -> Door (writer CITYGML_1)
Door (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_appearance{}.xlink_href xml_buffer, citygml_level_of_detail{} xml_buffer, citygml_address{}.xlink_href xml_buffer
_VegetationObject (writer CITYGML_1)
    attributes: citygml_target_uri xml_buffer, citygml_feature_role xml_buffer, citygml_feature_role_attr_name xml_buffer, citygml_feature_role_attr_val xml_buffer
TrafficArea (writer CITYGML_1)
    attributes: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
ReliefFeature (writer CITYGML_1)
    attributes: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
BreaklineRelief (writer CITYGML_1)
    attributes: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
ClosureSurface (writer CITYGML_1)
    attributes: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
_TransportationObject (writer CITYGML_1)
    attributes: citygml_target_uri xml_buffer, citygml_feature_role xml_buffer, citygml_feature_role_attr_name xml_buffer, citygml_feature_role_attr_val xml_buffer
TINRelief (writer CITYGML_1)
    attributes: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
CityObjectGroup (writer CITYGML_1)
    attributes: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
AuxiliaryTrafficArea (writer CITYGML_1)
    attributes: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
_WaterObject (writer CITYGML_1)
    attributes: citygml_target_uri xml_buffer, citygml_feature_role xml_buffer, citygml_feature_role_attr_name xml_buffer, citygml_feature_role_attr_val xml_buffer
RasterRelief (writer CITYGML_1)
    attributes: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
WaterClosureSurface (writer CITYGML_1)
    attributes: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
WaterSurface (writer CITYGML_1)
    attributes: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
WaterBody (writer CITYGML_1)
    attributes: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
WaterGroundSurface (writer CITYGML_1)
    attributes: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
MassPointRelief (writer CITYGML_1)
    attributes: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
LandUse (writer CITYGML_1)
    attributes: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
TransportationComplex (writer CITYGML_1)
    attributes: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
Square (writer CITYGML_1)
    attributes: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
Railway (writer CITYGML_1)
    attributes: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

Bookmark: Map layer names to qualifiers
  = Map layer names to qualifiers
Test_1_Level: Tester
    BOOL_OP = OR
    TEST_CLAUSE = TEST @Value(_hierarchy_count) = 1
    TEST_MODE = Automatic
    TEST_DESCRIPTION = ""
    PASSED -> AttributeCreator_10
AttributeCreator_10
    ATTR_LIST = gml_id,@Value(fme_basename)_@Value(_hierarchy{0}),gml_parent_id,@Value(fme_basename)
    -> AttributeCreator_11
AttributeCreator_11
    ATTR_LIST = extractSemantic,@Value(_hierarchy{0})
    -> AttributeSplitter_2
Test_2_Levels: Tester
    BOOL_OP = OR
    TEST_CLAUSE = TEST @Value(_hierarchy_count) = 2
    TEST_MODE = Automatic
    TEST_DESCRIPTION = ""
    PASSED -> AttributeCreator_2
    PASSED -> AttributeCreator
AttributeCreator
    ATTR_LIST = gml_id,@Value(fme_basename)_@Value(_hierarchy{0}),gml_parent_id,@Value(fme_basename)
    -> Aggregator
Aggregator
    ORDERED = No
    MODE = Attributes Only
    SEP = ,
    ACCUM_ATTRS_NAME = Yes
    GROUP_BY = gml_id
    AGGREGATE -> AttributeCreator_6
AttributeCreator_2
    ATTR_LIST = gml_id,@Value(fme_basename)_@Value(sketchup_extracted_layer),gml_parent_id,@Value(fme_basename)_@Value(_hierarchy{0})
    -> AttributeCreator_5
Test_3_Levels: Tester
    BOOL_OP = OR
    TEST_CLAUSE = TEST @Value(_hierarchy_count) = 3
    TEST_MODE = Automatic
    TEST_DESCRIPTION = ""
    PASSED -> AttributeCreator_3
AttributeCreator_3
    ATTR_LIST = gml_id,@Value(fme_basename)_@Value(sketchup_extracted_layer),gml_parent_id,@Value(fme_basename)_@Value(_hierarchy{0})_@Value(_hierarchy{1})
    -> AttributeCreator_14
AttributeCreator_14
    ATTR_LIST = Grand_Parent_id,@Value(fme_basename)_@Value(_hierarchy{0})
    -> AttributeCreator_5
AttributeCreator_5
    ATTR_LIST = extractSemantic,@Value(_hierarchy{@Evaluate(@Value(_hierarchy_count)-1)})
    -> AttributeSplitter_2
Test_4_Levels_3: Tester
    BOOL_OP = OR
    TEST_CLAUSE = TEST @Value(_hierarchy_count) = 3
    TEST_MODE = Automatic
    TEST_DESCRIPTION = ""
    PASSED -> AttributeCreator_12
AttributeCreator_12
    ATTR_LIST = gml_id,@Value(fme_basename)_@Value(sketchup_extracted_layer),gml_parent_id,@Value(fme_basename)_@Value(_hierarchy{0})_@Value(_hierarchy{1})
    -> AttributeCreator_13
AttributeCreator_13
    ATTR_LIST = extractSemantic,@Value(_hierarchy{@Evaluate(@Value(_hierarchy_count)-1)})
    -> AttributeCreator_6 [off]
    -> AttributeSplitter_2
AttributeCreator_6
    ATTR_LIST = extractSemantic,@Value(_hierarchy{0})
    -> Tester_4
Tester_4
    BOOL_OP = OR
    TEST_CLAUSE:
      TEST @Value(extractSemantic) BEGINS_WITH b
      TEST @Value(extractSemantic) BEGINS_WITH cityObject
    TEST_MODE = Automatic
    TEST_DESCRIPTION = ""
    PASSED -> AttributeSplitter_2
Test_4_Levels_2: Tester
    BOOL_OP = OR
    TEST_CLAUSE = TEST @Value(_hierarchy_count) = 4
    TEST_MODE = Automatic
    TEST_DESCRIPTION = ""
    PASSED -> AttributeCreator_15
AttributeCreator_15
    ATTR_LIST = gml_id,@Value(fme_basename)_@Value(sketchup_extracted_layer),gml_parent_id,@Value(fme_basename)_@Value(_hierarchy{0})_@Value(_hierarchy{1})_@Value(_hierarchy{2})
    -> AttributeCreator_16
AttributeCreator_16
    ATTR_LIST = extractSemantic,@Value(_hierarchy{@Evaluate(@Value(_hierarchy_count)-1)})
    -> AttributeSplitter_2
AttributeSplitter_2
    LIST_NAME = featureList
    ATTR_NAME = extractSemantic
    DELIMITER = -
    TRIM_OPTION = Both
    DROP_EMPTY_PARTS = No
    -> AttributeCreator_4
AttributeCreator_4
    ATTR_LIST = feature,@Value(featureList{0})
    -> AttributeValueMapper

Bookmark: Map qualifiers to CityGML classes
  = Map qualifiers to CityGML classes
AttributeValueMapper
    LUT = b,Building,cityObject,CityObject,add,Address,ws,WallSurface,gs,GroundSurface,rs,RoofSurface,cls,ClosureSurface,ofs,OuterFloorSurface,ocs,OuterCeilingSurface,d,Door,w,Window,obi,BuildingInstallation,ibi,InterioBuildingInstallation,fs,FloorSurface,iws,InteriorWallSurface,cs,CeilingSurface,bf,BuildingFurniture,room,Room,spc,PlantCover,r,Road,cf,CityFurniture,trk,Track,veg,Vegetation,office,Office
    DIRECTION = Forward (Source To Destination)
    VAL_ATTR = mappedFeature
    SRC = feature
    -> Scaler_2
Scaler_2
    YSCALE = 0
    TEXT_LOC_ONLY = Location and Size
    RASTER_SCALING = Extents
    ZSCALE = 0
    SCALE_ORIGIN = 0,0
    XSCALE = 0
    SCALED -> Offsetter_3
Offsetter_3
    XOFF = 2983460.574962016
    YOFF = 2178874.46332786
    ZOFF = 0
    MODE = Cartesian Coordinate
    OFFSET -> CoordinateSystemSetter_2
CoordinateSystemSetter_2
    COORDSYS = EPSG:24370
    -> AttributeFilter
AttributeFilter
    ATTR_NAME = mappedFeature
    ATTR_VALUES = Building,Address,WallSurface,GroundSurface,RoofSurface,ClosureSurface,OuterFloorSurface,OuterCeilingSurface,Door,Window,InterioBuildingInstallation,BuildingInstallation,FloorSurface,CeilingSurface,InteriorWallSurface,interiorFurniture,Room,Road,BuildingFurniture,CityFurniture,Track,CityObject,<Unfiltered>,Location Terrain,<Missing>,Location Snapshot,<Null>,<Empty>,PlantCover,Vegetation,Address,Office
    Address -> Aggregator_23
    WallSurface -> Aggregator_3
    WallSurface -> AttributeFilter_Building_-__AttributeCreator_18
    GroundSurface -> Aggregator_8
    GroundSurface -> AttributeFilter_Building_-__AttributeCreator_18
    RoofSurface -> Aggregator_9
    RoofSurface -> AttributeFilter_Building_-__AttributeCreator_18
    ClosureSurface -> Aggregator_14
    Door -> AppearanceSetter_2 [GEOMETRY]
    Door -> AttributeFilter_Building_-__AttributeCreator_18_Output_-__Aggregator_11 [off]
    Door -> AttributeFilter_FloorSurface_-__Aggregator_15
    Window -> WindowCounter
    Window -> AttributeFilter_Building_-__AttributeCreator_18_Output_-__Aggregator_11 [off]
    Window -> AttributeFilter_FloorSurface_-__Aggregator_15
    InterioBuildingInstallation -> Aggregator_22
    InterioBuildingInstallation -> AttributeFilter_Building_-__AttributeCreator_18
    BuildingInstallation -> Aggregator_2
    BuildingInstallation -> AttributeFilter_Building_-__AttributeCreator_18
    FloorSurface -> Aggregator_5
    FloorSurface -> Aggregator_21
    FloorSurface -> AttributeFilter_FloorSurface_-__Aggregator_15
    CeilingSurface -> Aggregator_4
    CeilingSurface -> Aggregator_21
    CeilingSurface -> AttributeFilter_FloorSurface_-__Aggregator_15
    InteriorWallSurface -> Aggregator_10
    InteriorWallSurface -> Aggregator_21
    InteriorWallSurface -> AttributeFilter_FloorSurface_-__Aggregator_15 [off]
    Room -> Aggregator_21
    Room -> Aggregator_7
    Road -> Aggregator_13
    BuildingFurniture -> Aggregator_20
    CityFurniture -> Aggregator_17
    Track -> Aggregator_18
    Location Terrain -> RasterBandRemover
    Location Snapshot -> RasterBandRemover
    PlantCover -> Aggregator_12
    Vegetation -> Aggregator_19
    Office -> Aggregator_24
Aggregator_23
    ORDERED = No
    MODE = Geometry - Assemble One Level
    SEP = ,
    ACCUM_ATTRS_NAME = Use Attributes From One Feature
    GROUP_BY = gml_parent_id
    AGGREGATE_TYPE = Homogeneous Collection (If Possible)
    AGGREGATE -> CityGMLGeometrySetter_7
CityGMLGeometrySetter_7
    GEOM = multiPoint
    ROLE = address
    -> Address (writer CITYGML_1)
Aggregator_3
    ORDERED = No
    MODE = Geometry - Assemble One Level
    SEP = ,
    ACCUM_ATTRS_NAME = Yes
    GROUP_BY = gml_id
    AGGREGATE_TYPE = Homogeneous Collection (If Possible)
    AGGREGATE -> AttributeCreator_19
AttributeCreator_19
    ATTR_TABLE = SET_TO gml_name = @Value(gml_id)-Wall-Surface
    -> CityGML_Role_Setter_2
CityGML_Role_Setter_2
    ROLE = boundedBy
    -> CityGML_LOD_Setter
CityGML_LOD_Setter
    GEOM = lod4MultiSurface
    LOD = 4
    -> CityGML_LOD_Setter_Output_-__Scaler
CityGML_LOD_Setter_Output_-__Scaler: Junction
    -> Scaler [off]
    -> WallSurface (writer CITYGML_1)
Aggregator_14
    ORDERED = No
    MODE = Geometry - Assemble One Level
    SEP = ,
    ACCUM_ATTRS_NAME = Yes
    GROUP_BY = gml_id
    AGGREGATE_TYPE = Homogeneous Collection (If Possible)
    AGGREGATE -> CityGML_Role_Setter_15
CityGML_Role_Setter_15
    ROLE = boundedBy
    -> CityGML_LOD_Setter_18
CityGML_LOD_Setter_18
    GEOM = lod4MultiSurface
    LOD = 4
    -> Building (writer CITYGML_1) [off]
Aggregator_8
    ORDERED = No
    MODE = Geometry - Assemble One Level
    SEP = ,
    ACCUM_ATTRS_NAME = Yes
    GROUP_BY = gml_id
    AGGREGATE_TYPE = Homogeneous Collection (If Possible)
    AGGREGATE -> CityGML_Role_Setter_5
CityGML_Role_Setter_5
    ROLE = boundedBy
    -> CityGML_LOD_Setter_10
CityGML_LOD_Setter_10
    GEOM = lod4MultiSurface
    LOD = 4
    -> GroundSurface (writer CITYGML_1)
Aggregator_9
    ORDERED = No
    MODE = Geometry - Assemble One Level
    SEP = ,
    ACCUM_ATTRS_NAME = Yes
    GROUP_BY = gml_id
    AGGREGATE_TYPE = Homogeneous Collection (If Possible)
    AGGREGATE -> CityGML_Role_Setter_9
CityGML_Role_Setter_9
    ROLE = boundedBy
    -> CityGML_LOD_Setter_11
CityGML_LOD_Setter_11
    GEOM = lod4MultiSurface
    LOD = 4
    -> RoofSurface (writer CITYGML_1)
AttributeFilter_FloorSurface_-__Aggregator_15: Junction
    -> AttributeFilter_Building_-__AttributeCreator_18 [off]
AttributeFilter_Building_-__AttributeCreator_18: Junction
    -> Aggregator_11
Aggregator_11
    ORDERED = No
    MODE = Geometry - Assemble One Level
    SEP = ,
    ACCUM_ATTRS_NAME = Use Attributes From One Feature
    GROUP_BY = gml_parent_id
    AGGREGATE_TYPE = Homogeneous Collection (If Possible)
    AGGREGATE -> AttributeCreator_18
AttributeCreator_18
    ATTR_TABLE:
      SET_TO gml_name = MAIN-BUILDING
      SET_TO gml_id = @Value(gml_parent_id)
      SET_TO gml_parent_id = @Value(Grand_Parent_id)
    -> CityGML_Role_Setter [off]
    -> CityGMLGeometrySetter_8
CityGML_LOD_Setter_8 [off]
    GEOM = lod3TerrainIntersection
    LOD = 4
    -> CityGML_LOD_Setter_4_Output_-__Scaler [off]
CityGML_LOD_Setter_9 [off]
    GEOM = lod4Solid
    LOD = 4
    -> CityGML_LOD_Setter_4_Output_-__Scaler [off]
CityGML_LOD_Setter_4_Output_-__Scaler: Junction
    -> Scaler [off]
    -> BuildingPart (writer CITYGML_1) [off]
CityGMLGeometrySetter_8
    GEOM = lod4MultiSurface
    ROLE = cityObjectMember
    -> BoundsExtractor_2
BoundsExtractor_2
    XMIN = _xmin
    ZMAX = _zmax
    YMAX = _ymax
    ZMIN = _zmin
    XMAX = _xmax
    YMIN = _ymin
    -> ExpressionEvaluator_2
ExpressionEvaluator_2
    ACTION = Create New Attribute
    VAL_ATTR = citygml_measured_height
    EXPRESSION = @Value(_zmax) - @Value(_zmin)
    -> AttributeCreator_20
AttributeCreator_20
    ATTR_TABLE:
      SET_TO citygml_measured_height_units = #m
      SET_TO citygml_roof_type = 1000
      SET_TO citygml_year_of_construction = 1990
    -> AttributeCreator_20_OUTPUT_-__AppearanceSetter_GEOMETRY
WindowCounter: Counter
    DOMAIN = windowcounter
    CNT_ATTR = window_count
    SCOPE = Local
    START = 1
    -> AttributeCreator_9
AttributeCreator_9
    ATTR_LIST = gml_id,@Value(gml_id)-@Value(window_count)
    -> CityGML_Role_Setter_10
CityGML_Role_Setter_10
    ROLE = opening
    -> CityGML_LOD_Setter_12
CityGML_LOD_Setter_12
    GEOM = lod4MultiSurface
    LOD = 4
    -> Window (writer CITYGML_1)
Aggregator_2
    ORDERED = No
    MODE = Geometry - Assemble One Level
    SEP = ,
    ACCUM_ATTRS_NAME = Yes
    GROUP_BY = gml_id
    AGGREGATE_TYPE = Homogeneous Collection (If Possible)
    AGGREGATE -> CityGMLGeometrySetter_5
CityGMLGeometrySetter_5
    GEOM = lod4Geometry
    ROLE = outerBuildingInstallation
    -> CityGML_LOD_Setter_3
CityGML_LOD_Setter_3
    GEOM = lod4Geometry
    LOD = 4
    -> Scaler [off]
    -> BuildingInstallation (writer CITYGML_1)
Aggregator_22
    ORDERED = No
    MODE = Geometry - Assemble One Level
    SEP = ,
    ACCUM_ATTRS_NAME = Yes
    GROUP_BY = gml_id
    AGGREGATE_TYPE = Homogeneous Collection (If Possible)
    AGGREGATE -> CityGMLGeometrySetter_6
CityGMLGeometrySetter_6
    GEOM = lod4Geometry
    ROLE = interiorBuildingInstallation
    -> CityGML_LOD_Setter_25
CityGML_LOD_Setter_25
    GEOM = lod4Geometry
    LOD = 4
    -> IntBuildingInstallation (writer CITYGML_1)
Aggregator_5
    ORDERED = No
    MODE = Geometry - Assemble One Level
    SEP = ,
    ACCUM_ATTRS_NAME = Yes
    GROUP_BY = gml_id
    AGGREGATE_TYPE = Homogeneous Collection (If Possible)
    AGGREGATE -> CityGML_Role_Setter_6
CityGML_Role_Setter_6
    ROLE = boundedBy
    -> CityGML_LOD_Setter_5
Aggregator_4
    ORDERED = No
    MODE = Geometry - Assemble One Level
    SEP = ,
    ACCUM_ATTRS_NAME = Yes
    GROUP_BY = gml_id
    AGGREGATE_TYPE = Homogeneous Collection (If Possible)
    AGGREGATE -> CityGML_Role_Setter_11
CityGML_Role_Setter_11
    ROLE = boundedBy
    -> CityGML_LOD_Setter_13
CityGML_LOD_Setter_13
    GEOM = lod4MultiSurface
    LOD = 4
    -> CeilingSurface (writer CITYGML_1)
Aggregator_10
    ORDERED = No
    MODE = Geometry - Assemble One Level
    SEP = ,
    ACCUM_ATTRS_NAME = Yes
    GROUP_BY = gml_id
    AGGREGATE_TYPE = Homogeneous Collection (If Possible)
    AGGREGATE -> CityGML_Role_Setter_12
CityGML_Role_Setter_12
    ROLE = boundedBy
    -> CityGML_LOD_Setter_14
CityGML_LOD_Setter_14
    GEOM = lod4MultiSurface
    LOD = 4
    -> InteriorWallSurface (writer CITYGML_1)
Aggregator_7
    ORDERED = No
    MODE = Geometry - Assemble One Level
    SEP = ,
    ACCUM_ATTRS_NAME = Yes
    GROUP_BY = gml_parent_id
    AGGREGATE_TYPE = Homogeneous Collection (If Possible)
    AGGREGATE -> CityGML_Role_Setter_8
CityGML_Role_Setter_8
    ROLE = interiorRoom
    -> CityGML_LOD_Setter_5 [off]
    -> CityGML_LOD_Setter_15
CityGML_LOD_Setter_5
    GEOM = lod4MultiSurface
    LOD = 4
    -> Scaler [off]
    -> FloorSurface (writer CITYGML_1)
CityGML_LOD_Setter_15
    GEOM = lod3MultiSurface
    LOD = 4
Aggregator_12
    ORDERED = No
    MODE = Geometry - Assemble One Level
    SEP = ,
    ACCUM_ATTRS_NAME = Yes
    GROUP_BY = gml_id
    AGGREGATE_TYPE = Homogeneous Collection (If Possible)
    AGGREGATE -> CityGMLGeometrySetter_2
CityGMLGeometrySetter_2
    GEOM = lod4Geometry
    ROLE = cityObjectMember
    -> SolitaryVegetationObject (writer CITYGML_1)
Aggregator_13
    ORDERED = No
    MODE = Geometry - Assemble One Level
    SEP = ,
    ACCUM_ATTRS_NAME = Yes
    GROUP_BY = gml_parent_id
    AGGREGATE_TYPE = Homogeneous Collection (If Possible)
    AGGREGATE -> CityGML_Role_Setter_13
CityGML_Role_Setter_13
    ROLE = trafficArea
    -> CityGML_LOD_Setter_17
CityGML_LOD_Setter_17
    GEOM = lod4MultiSurface
    LOD = 4
    -> Road (writer CITYGML_1)
Aggregator_17
    ORDERED = No
    MODE = Geometry - Assemble One Level
    SEP = ,
    ACCUM_ATTRS_NAME = Yes
    GROUP_BY = gml_parent_id
    AGGREGATE_TYPE = Homogeneous Collection (If Possible)
    AGGREGATE -> CityGMLGeometrySetter_3
DoorCounter: Counter
    DOMAIN = doorcounter
    CNT_ATTR = door_count
    SCOPE = Local
    START = 1
    -> AttributeCreator_8
AttributeCreator_8
    ATTR_LIST = gml_id,@Value(gml_id)-@Value(door_count)
    -> CityGML_Role_Setter_3
CityGML_Role_Setter_3
    ROLE = opening
    -> CityGML_LOD_Setter_2
CityGML_LOD_Setter_2
    GEOM = lod4MultiSurface
    LOD = 4
    -> Door (writer CITYGML_1)

FME custom transformer CityGML_LOD_Setter

Parameters:
- LOD =   # Level of detail
- GEOM =   # CityGML Geometry Type

Input (input)
    -> AttributeCreator_3
Note: Set level of detail / and geometry type
AttributeCreator_3
    ATTR_LIST = citygml_level_of_detail,$(LOD),citygml_lod_name,$(GEOM)
    -> GeometryTraitSetter
Note: Attach geometry as trait
GeometryTraitSetter
    OVERWRITE_CHOICE = Yes
    SRC_ATTRS = citygml_lod_name
    -> Output (output)
Output (output)

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    GQUERY:
      for $geom in //geometry
      where $geom/count(parent::geometry) = 0
      return number($geom/@fme_id)
    OVERWRITE_CHOICE = Yes
    SETTYPE_PARAM = Traits From Attributes
    SRC_ATTRS = citygml_lod_name
    REMOVE_ATTRIBUTE = No
    SET -> Output (output)
Output (output)

FME custom transformer CityGML_Role_Setter

Parameters:
- ROLE =   # CityGML Role

Input (input)
    -> AttributeCreator
Note: Set role
AttributeCreator
    ATTR_LIST = citygml_feature_role,$(ROLE)
    -> Output (output)
Output (output)

FME custom transformer AttributeSwapper
Swaps the values and internal storage data types of specified two attributes (A and B).
By default, swapping will be performed unconditionally, but optionally you can choose one of these conditional swapping modes. 
"A < B" [A_LT_B]: Swap the values only when A is less than B. 
"A > B" [A_GT_B]: Swap the values only when A is greater than B. 
Leading/trailing spaces and leading zeros will be ignored when the values are being compared as NUMERIC; will NOT be ignored when the values are being compared as STRING.
The <null> and <missing> will also be swapped, but those will be treated as the empty string when comparing values in conditional swapping mode. 
A new attribute called "_swapped" will be added to the output features; its value indicates whether the two attribute values have been swapped. 
_swapped = 1: the values have been swapped. 
_swapped = 0: the values have not been swapped.
Only when you set "A < B" or "A > B" to the "Swapping Condition" parameter and set "Numeric" to the "Comparison Mode" parameter, the input feature will be output via the <Rejected> port if a specified attribute stores a non-numeric value.
Parameters 
Attribute A / Attribute B : 
Select two attributes whose values should be swapped. 
Swap Condition :
Select one of these swapping condition. 
"Unconditional" [UNCONDITIONAL]: Swap the values unconditionally (default). 
"A < B" [A_LT_B]: Swap the values only when A is less than B. 
"A > B" [A_GT_B]: Swap the values only when A is greater than B. 
Comparison Mode :
Select one of these comparison mode for conditional swapping. This parameter setting will be just ignored when you have set "Unconditional" to the "Swap Condition" parameter.
"Automatic": The transformer will compare the values as numeric values if possible, and as strings otherwise. 
"String": The transformer will always compare the values as strings.
"Numeric": The transformer will always compare the values as numeric values. If a value is not numeric, the input feature will be output via the <Rejected> port (only when you have set "A < B" or "A > B" to the "Swap Condition" parameter).

Parameters:
- ATTR_A =   # " " Attribute A
- ATTR_B =   # " " Attribute B
- CONDITION = UNCONDITIONAL   # < B,A_LT_B%A > B,A_GT_B Swap Condition
- COMP_MODE = Automatic   # Comparison Mode

Input (input)
    -> ParameterFetcher
ParameterFetcher
    ATTR_LIST = __attributeswapper.attr_a {$(ATTR_A)} __attributeswapper.attr_b {$(ATTR_B)} __attributeswapper.condition {$(CONDITION)} __attributeswapper.comp_mode {$(COMP_MODE)}
    -> TclCaller
TclCaller
    TCLPROG = swapAttributes
    VAL_ATTR = _swapped
    SRC:
      proc swapAttributes {} {
          set result -1
          set attr_a [FME_GetAttribute "__attributeswapper.attr_a"]
          set attr_b [FME_GetAttribute "__attributeswapper.attr_b"]
          set condition [FME_GetAttribute "__attributeswapper.condition"]
          if {[string equal $condition "UNCONDITIONAL"]} {
              set result 1
          } else {
              proc trimLeftZero {s} {
                  set v [string trimleft [set t [string trim $s]] {0}]
                  if {[string length $v]==0 && 0<[string length $t]} {
                      return 0
                  } else {
                      return $v
                  }
              }
              set a [FME_GetAttribute $attr_a]
              set b [FME_GetAttribute $attr_b]
              set mode [FME_GetAttribute "__attributeswapper.comp_mode"]
              switch $mode {
                  "String" {
                      switch $condition {
                          "A_LT_B" {set result [expr [string compare $a $b] < 0]}
                          "A_GT_B" {set result [expr [string compare $a $b] > 0]}
                      }
                  }
                  default {
                      set x [trimLeftZero $a]
                      set y [trimLeftZero $b]
                      if {[string is double -strict $x] && [string is double -strict $y]} {
                          switch $condition {
                              "A_LT_B" {set result [expr $x < $y]}
                              "A_GT_B" {set result [expr $x > $y]}
                          }
                      } elseif {[string equal $mode "Automatic"]} {
                          switch $condition {
                              "A_LT_B" {set result [expr [string compare $a $b] < 0]}
                              "A_GT_B" {set result [expr [string compare $a $b] > 0]}
                          }
                      }
                  }
              }
          }
          if {$result == 1} {
              FME_RenameAttribute "__attributeswapper.tmp" $attr_a
              FME_RenameAttribute $attr_a $attr_b
              FME_RenameAttribute $attr_b "__attributeswapper.tmp"
          }
          return $result
      }
    -> Tester
Tester
    BOOL_OP = OR
    TEST_CLAUSE = TEST 0 <= @Value(_swapped)
    TEST_MODE = Automatic
    TEST_DESCRIPTION = ""
    PASSED -> Output (output)
    FAILED -> <Rejected> (output)
Output (output)
<Rejected> (output)

FME custom transformer SketchupLayerExtractor

Input (input)
    -> Deaggregator
Deaggregator
    PART_NUMBER_FIELD = _part_number
    ID_ATTR = _hierarchy_id
    SPLIT_COMPOSITES = No
    GEOM_NAME_FIELD = _geometry_name
    LIST_ATTR_MODE_LOOKUP = LEAN
    COPY_ATTR = Every Node
    ID_SELECTION = ID and Parent ID
    CHILD_ID_ATTR = _hierarchy_child_id_list
    EXPLODE_INSTANCES = No
    PARENT_ID_ATTR = _hierarchy_parent_id
    MODE = Flatten One Level
    DEAGGREGATED -> AttributeRemover
AttributeRemover
    LIST_ATTRS = _hierarchy_child_id_list{}
    REMOVE_ATTRS = _geometry_name,_hierarchy_id,_hierarchy_parent_id,_part_number
    -> GeometryPropertyExtractor
GeometryPropertyExtractor
    PREFIX_EXTRACTED_TRAITS = No
    EXTRACTTYPE_PARAM = Traits
    TRAIT_ATTR_LIST = sketchup_layer_name
    EXTRACTED -> AttributeRenamer
    UNTOUCHED -> Untouched (output)
AttributeRenamer
    ATTR_LIST = sketchup_layer_name,sketchup_extracted_layer,""
    -> Extracted (output)
Extracted (output)
Untouched (output)

FME custom transformer AttributeConcatenator
Concatenates selected attribute values in the order specified to the "Concatenating Order" parameter.
Resulting string consists of the original attribute values delimited by identical string specified to the "Separator String" parameter.
This transformer considers both Null value and Missing attribute as an empty string. 
See also the AttributeListPopulator.
Parameters
Attributes to Concatenate:
Select attributes which should be concatenated.
Concatenating Order:
Choose one of these as the concatenating order.
- Value Numeric Ascending: sorted by attribute value numeric ascending
- Value Numeric Descending: sorted by attribute value numeric descending
- Value Alphabetic Ascending: sorted by attribute value alphabetic ascending
- Value Alphabetic Descending: sorted by attribute value alphabetic descending
- Name Ascending (Alphabetic): sorted by attribute name alphabetic ascending
- Name Descending (Alphabetic): sorted by attribute name alphabetic descending
Note:
In "Value Numeric Ascending/Descending", the transformer considers every non-numeric value (including empty/null/missing) as 0.
But a numeric representation surrounded by white spaces will be treated as a numeric value (both leading and trailing white spaces will be ignored).
And leading 0 of a numeric representation will also be ignored when comparing it as a numeric value to other values.
Case Sensitive:
Yes: The transformer will perform case-sensitive sorting.
No (default): The transformer will perform case-insensitive sorting.
Note
The "Case Sensitive" parameter setting is basically applied to alphabetic sorting, but it will also be applied to non-numeric parts in numeric sorting, if non-numeric values exist.
Separator String:
Specify a string that will be used as the delimiter. You can set blank to this parameter not to use delimiter.
Trim Whitespaces:
By default, the transformer will remove Both leading and trailing whitespaces from every original attribute value before concatenating, but you can change the setting to either Left or Right, or None.
Destination Attribute:
Specify name of the attribute that stores the resulting string.
Drop Empty Parts:
Yes: The concatenation will be performed excluding empty parts.
No (default): The concatenation will be performed including empty parts.

Parameters:
- ATTRS =   # " " Attributes to Concatenate
- ORDER = ValueNumericAscending
- CASE = No   # Case Sensitive
- SEP = ,   # Separator String
- TRIM_OPTION = Both   # Trim Whitespaces
- DEST_ATTR = _concatenated   # TYPE:varchar(200) Destination Attribute
- DROP_EMPTY_PARTS = No   # Drop Empty Parts

Input (input)
    -> ParameterFetcher
ParameterFetcher
    ATTR_LIST = attributeconcatenator.attrs {$(ATTRS)} attributeconcatenator.sep {$(SEP)} attributeconcatenator.order {$(ORDER)} attributeconcatenator.case {$(CASE)} attributeconcatenator.trim_option {$(TRIM_OPTION)} attributeconcatenator.drop_empty {$(DROP_EMPTY_PARTS)}
    -> TclCaller
TclCaller
    TCLPROG = concatAttrs
    VAL_ATTR = attributeconcatenator.dest_attr
    SRC:
      proc concatAttrs {} {
          set attrs [FME_GetAttribute "attributeconcatenator.attrs"];
          set order [FME_GetAttribute "attributeconcatenator.order"];
          set nocase [string equal [FME_GetAttribute "attributeconcatenator.case"] {No}];
          set trimOption [FME_GetAttribute "attributeconcatenator.trim_option"];
          set trimOption [string map {Both trim Left trimleft Right trimright None ""} $trimOption];
          set keepEmpty [string equal [FME_GetAttribute "attributeconcatenator.drop_empty"] {No}];
          set sorted {};
          proc getAttr {name trimOption} {
              if {[string equal $trimOption {}]} {
                  return [FME_GetAttribute $name];
              } else {
                  return [string $trimOption [FME_GetAttribute $name]];
              };
          };
          if {[regexp {^ValueNumeric.+} $order]} {
              set num {}; set nan {};
              foreach name $attrs {
                  set v [getAttr $name $trimOption];
                  if {$keepEmpty || ![string equal $v {}]} {
                      set t [string trim $v]
                      set n [string trimleft [string range $t 0 end-1] {0}][string index $t end];
                      if {[string is double -strict $n]} {
                          lappend num [list $n $v];
                      } else {
                          lappend nan [list {0} $v];
                      };
                  };
              };
              if {$nocase} {
                  set nan [lsort -nocase -index 1 $nan];
              } else {
                  set nan [lsort -index 1 $nan];
              };
              foreach vv [lsort -real -index 0 [concat $nan $num]] {
                  lappend sorted [lindex $vv 1];
              };
          } elseif {[regexp {^ValueAlphabetic.+} $order]} {
              foreach name $attrs {
                  set v [getAttr $name $trimOption];
                  if {$keepEmpty || ![string equal $v {}]} {
                      lappend sorted $v;
                  };
              };
              if {$nocase} {
                  set sorted [lsort -nocase $sorted];
              } else {
                  set sorted [lsort $sorted];
              };
          } elseif {[regexp {^Name.+} $order]} {
              if {$nocase} {
                  set attrs [lsort -nocase $attrs];
              } else {
                  set attrs [lsort $attrs];
              };
              foreach name $attrs {
                  set v [getAttr $name $trimOption];
                  if {$keepEmpty || ![string equal $v {}]} {
                      lappend sorted $v;
                  };
              };
          } else {
              return "Debug: Invalid Concatenation Order: $order";
          };
          set delim [FME_GetAttribute "attributeconcatenator.sep"];
          if {[regexp {.+Ascending$} $order]} {
              return [join $sorted $delim];
          } elseif {[regexp {.+Descending$} $order]} {
              return [join [lreverse $sorted] $delim];
          } else {
              return "Debug: Invalid Concatenation Order: $order";
          };
      }
    -> BulkAttributeRenamer
BulkAttributeRenamer
    ATTRCHOICE = Selected Attributes
    REPLACE_STR = $(DEST_ATTR)
    REPLACE_PATTERN = .+
    PATTERN_ACTION_DISP = Regular Expression Replace
    ATTRLIST = attributeconcatenator.dest_attr
    -> BulkAttributeRemover
BulkAttributeRemover
    ATTR_EXP = ^attributeconcatenator.+
    -> Output (output)
Output (output)
